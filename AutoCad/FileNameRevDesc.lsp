(defun c:demo (/ hms:get_atts filename hnd layouts lst lst1 name otab path ss)

  (defun hms:get_atts (enm / att obj)
    (if (or (and (eq (type enm) 'ENAME)
                 (setq obj (vlax-ename->vla-object enm))
                 (eq (vla-get-hasattributes obj) :vlax-true)
            )
            (and (eq (type enm) 'VLA-OBJECT)
                 (setq obj enm)
                 (eq (vla-get-hasattributes obj) :vlax-true)
            )
        )
      (mapcar
        '(lambda (att)
           (cons (vla-get-TagString att) (vla-get-TextString att))
         )
        (vlax-invoke obj "GetAttributes")
      )
    )
  )

  (if (and (setq path (acet-ui-pickdir "Select directory" (getvar "dwgprefix")))
           (setq ss (ssget "_X" (list '(0 . "INSERT") '(2 . "BBORDER") '(66 . 1) (cons 410 (getvar 'CTAB)))))
      )
    (progn
      (setq hnd  (ssname ss 0)
            lst  (hms:get_atts hnd)
            lst1 '("DWG#" "ACAD_REVNO_CURRENT" "ACAD_TEXT3")
            name ""
      )
      (foreach n lst1
        (if (setq a (assoc n lst))
          (setq name (strcat name "-" (cdr a)))
        )
      )
      (setq filename (strcat path "\\" (vl-string-left-trim "-" name) ".pdf"))
      (command "_.-export" "Pdf" "_E" "_NO" filename)
    )
  )
  (princ)
)
